FME workspace TP2.fmw

Parameters:
- SourceDataset_CSV2 = https://donnees.montreal.ca/fr/dataset/575ecf37-9097-44cd-817f-a2fbd8de314b/resource/3fa557d2-c3b2-49a9-8d32-081c64d20d89/download/stationnements-h-2024-2025.csv   # Source CSV (Comma Separated Value) File(s)
- SourceDataset_CSV2_5 = $(FME_MF_DIR)stationnements-h-2024-2025.csv   # Source CSV (Comma Separated Value) File(s)
- SourceDataset_GEOJSON = https://donnees.montreal.ca/dataset/9797a946-9da8-41ec-8815-f6b276dec7e9/resource/6b313375-d9bc-4dc3-af8e-ceae3762ae6e/download/limites-administratives-agglomeration-nad83.geojson   # Source GeoJSON File or URL
- SourceDataset_SHAPEFILE = $(FME_MF_DIR)stm_sig\stm_arrets_sig.shp   # Source Esri Shapefile(s)
- DestDataset_POSTGIS_5 = geo7630   # Connection
- DestDataset_POSTGIS_7 = geo7630   # Connection
- DestDataset_POSTGIS_6 = geo7630   # Connection
- DestDataset_POSTGIS = geo7630   # Connection

Readers:
- CSV2_1: CSV2 from $(SourceDataset_CSV2)
- CSV2_2: CSV2 from $(SourceDataset_CSV2_5)
- GEOJSON_1: GEOJSON from $(SourceDataset_GEOJSON)
- SHAPEFILE_1: SHAPEFILE from $(SourceDataset_SHAPEFILE)

Writers:
- POSTGIS_1: POSTGIS to $(DestDataset_POSTGIS)
- POSTGIS_2: POSTGIS to $(DestDataset_POSTGIS_5)
- POSTGIS_3: POSTGIS to $(DestDataset_POSTGIS_7)
- POSTGIS_4: POSTGIS to $(DestDataset_POSTGIS_6)

AttributeManager_4
    ATTR_TABLE:
      REMOVE BOROUGH (varchar(41))
      REMOVE X (real64)
      REMOVE Y (real64)
      REMOVE JURIDICTION (varchar(24))
      REMOVE LOCATION (varchar(98))
      REMOVE HEURES (varchar(21))
      REMOVE HOURS (varchar(23))
      REMOVE NOTE_FR (varchar(101))
      REMOVE NOTE_EN (varchar(98))
      REMOVE TYPE_PAY (uint32)
    -> NeighborFinder [CANDIDATE]
H3HexagonalIndexer__Rejected_: Logger
    LOG_FEATURE = LOG_ONLY
    MAXCOORDS = 20
    MAXFEATS = 20
    MESSAGE = Feature is:
    SEVERITY = INFO

Bookmark: Analyse de proximité des stationnements avec les réseaux de transports en communs
Note: Données en entrée des points de stations/arrets transport en commun
stm_arrets_sig (reader SHAPEFILE_1)
    attributes: stop_code long, stop_id varchar(8), stop_name varchar(75), stop_url varchar(100), wheelchair short, route_id varchar(64), loc_type short, shelter short, service_id varchar(3)
    -> EsriReprojector_3
Note: Reprojection en EPSG : 3857
EsriReprojector_3
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_NAME = NAD_1983_CSRS_To_WGS_1984
    INTERPOLATION_TYPE = ,NearestNeighbor
    RASTER_CELL_SIZE_LOOKUP = ,PreserveCells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    INTERPOLATION_TYPE_NAME = Nearest Neighbor
    RASTER_CELL_SIZE = Preserve Cells
    REPROJECTED -> AttributeManager_3
Note: Nettoyage des attributs
Note: Nettoyer les attributs de stationnements nécessaires pour l'analyse de proximité
AttributeManager_3
    ATTR_TABLE:
      REMOVE stop_code (int32)
      REMOVE wheelchair (int16)
      REMOVE route_id (varchar(64))
      REMOVE shelter (int16)
      REMOVE service_id (varchar(3))
    -> NeighborFinder [BASE]
Note: identification des arrets de transports les plus proches pour chaque stationnements dans un rayon de 500m
NeighborFinder
    ATTR_ACCUM_MODE = Merge Candidate
    ATTR_CONFLICT_RES = Use Candidate
    CANDIDATES_FIRST = Yes
    INSERT_VERTEX = No
    K = 1
    MAX = 500
    MEASURES_FROM_CANDIDATE = Yes
    MEASURE_TYPE = Continuous
    MODE = Bases and Candidates
    TREAT_POLYGON_AS = Lines
    MATCHED -> AttributeManager_5
Note: Nettoryage des attributs et renom pour faciliter la compréhension
AttributeManager_5
    ATTR_TABLE:
      REMOVE NBR_PLA (uint32)
      RENAME_SET_VALUE EMPLACEMENT > EMPLACEMENT_Stationnement (varchar(114))
      RENAME_SET_VALUE stop_id > ID_arret (varchar(8))
      RENAME_SET_VALUE stop_name > Nom_arret (varchar(75))
      RENAME_SET_VALUE loc_type > Type de transport (0=Bus_2=Métro) (int16)
      RENAME_SET_VALUE _distance > Distance(m) (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
    -> Arrets_Stationnement (writer POSTGIS_1)
Arrets_Stationnement (writer POSTGIS_1)
    attributes: id_sta int8, arrondissement varchar(41), emplacement_stationnement varchar(114), id_arret varchar(8), nom_arret varchar(75), stop_url varchar(100), type_de_transport__0=bus_2=métro_ int2, distance_m_ float8

Bookmark: 1- Stationnements Gratuits et Disponible par Arrondissement et leur Nombre
Note: CSV: stationnements
CSV (reader CSV2_2)
    attributes: ID_STA uint32, ARRONDISSEMENT varchar(41), BOROUGH varchar(41), NBR_PLA uint32, X x_coordinate, Y y_coordinate, JURIDICTION varchar(24), EMPLACEMENT varchar(114), LOCATION varchar(98), HEURES varchar(21), HOURS varchar(23), NOTE_FR varchar(101), NOTE_EN varchar(98), TYPE_PAY uint32
    -> VertexCreator
Note: Transformation des coordonnées X Y en point
VertexCreator
    MEASURE_TYPE_LOOKUP = CONTINUOUS
    MODE = REPLACE
    REMOVE_ATTRIBUTES = No
    XVAL = @Value(X)
    YVAL = @Value(Y)
    MEASURE_TYPE = Continuous
    MODE_NAME = Replace with Point
    -> EsriReprojector_2
    -> Reprojector
EsriReprojector_2
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_NAME = NAD_1983_To_WGS_1984_1
    INTERPOLATION_TYPE = ,NearestNeighbor
    RASTER_CELL_SIZE_LOOKUP = ,PreserveCells
    RASTER_TOLERANCE = 0.0
    SOURCE = ESRIWKT|NAD_1983_MTM_8|PROJCS["NAD_1983_MTM_8",GEOGCS["GCS_North_American_1983",DATUM["D_North_American_1983",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    INTERPOLATION_TYPE_NAME = Nearest Neighbor
    RASTER_CELL_SIZE = Preserve Cells
    REPROJECTED -> PointOnAreaOverlayer [POINT]
    REPROJECTED -> AttributeManager_4
Note: limites-administratives Montréal
limites-administratives-agglomeration-nad83 (reader GEOJSON_1)
    attributes: CODEID int, NOM string, NOM_OFFICIEL string, CODEMAMH string, CODE_3C string, NUM int, ABREV string, TYPE string, COMMENT string, DATEMODIF string
    -> EsriReprojector
EsriReprojector
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_NAME = NAD_1983_To_WGS_1984_1
    INTERPOLATION_TYPE = ,NearestNeighbor
    RASTER_CELL_SIZE_LOOKUP = ,PreserveCells
    RASTER_TOLERANCE = 0.0
    SOURCE = ESRIWKT|NAD_1983_MTM_8|PROJCS["NAD_1983_MTM_8",GEOGCS["GCS_North_American_1983",DATUM["D_North_American_1983",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    INTERPOLATION_TYPE_NAME = Nearest Neighbor
    RASTER_CELL_SIZE = Preserve Cells
    REPROJECTED -> PointOnAreaOverlayer [AREA]
PointOnAreaOverlayer
    DEAGGREGATE_INPUT = Yes
    OV_ATTR = point_count
    POLYS_FIRST = NO
    POINT -> AttributeManager_2
    AREA -> AttributeManager
Note: Nbre de places de stationnements en déneigements avec restrictions horaires
AttributeManager_2
    ATTR_TABLE:
      REMOVE BOROUGH (varchar(41))
      REMOVE X (real64)
      REMOVE Y (real64)
      REMOVE JURIDICTION (varchar(24))
      REMOVE LOCATION (varchar(98))
      REMOVE HOURS (varchar(23))
      REMOVE NOTE_EN (varchar(98))
      REMOVE TYPE_PAY (uint32)
      REMOVE point_count (uint32)
    -> Nbres_de_places_et_heures_de_stationnement (writer POSTGIS_2)
Nbres_de_places_et_heures_de_stationnement (writer POSTGIS_2)
    attributes: id_sta int8, arrondissement varchar(41), nbr_pla int8, emplacement varchar(114), heures varchar(21), note_fr varchar(101)
Note: Reprojection des arrondissements en 4326 pour la création de tuiles hexagonales
AttributeManager
    ATTR_TABLE:
      REMOVE CODEID (int64)
      REMOVE NOM_OFFICIEL (buffer)
      REMOVE CODEMAMH (buffer)
      REMOVE CODE_3C (buffer)
      REMOVE NUM (int64)
      REMOVE ABREV (buffer)
      REMOVE COMMENT (buffer)
      REMOVE DATEMODIF (buffer)
      RENAME_SET_VALUE point_count > nbre_site_stationnement (uint32)
    -> Nbre_de_site (writer POSTGIS_3)
    -> EsriReprojector_4
Note: H3HexagonalIndexer__Rejected_
Nbre_de_site (writer POSTGIS_3)
    attributes: nom varchar, type varchar, nbre_site_stationnement int8

Bookmark: Créeation de tuiles hexagonales pour la densité
Note: Reprojection en 4326 pour la création de tuiles hexagonales pour le CSV
Reprojector
    DEST = EPSG:4326
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> PointOnAreaOverlayer_2 [POINT]
EsriReprojector_4
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_NAME = <None>
    INTERPOLATION_TYPE = ,NearestNeighbor
    RASTER_CELL_SIZE_LOOKUP = ,PreserveCells
    RASTER_TOLERANCE = 0.0
    SOURCE = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    INTERPOLATION_TYPE_NAME = Nearest Neighbor
    RASTER_CELL_SIZE = Preserve Cells
    REPROJECTED -> H3HexagonalIndexer
Note: Création de tuiles hexagonales
H3HexagonalIndexer
    INDEX_OPERATION = Filling Indexes
    -> Dissolver
    <REJECTED> -> H3HexagonalIndexer__Rejected_
Note: Pour dissoudre les tuiles
Dissolver
    ACCUM_INPUT_ATTRS = Merge Incoming Attributes
    CLEANING_TOLERANCE_LOOKUP = AUTO
    CONNECT_Z_MODE_LOOKUP = FIRST_WINS
    DEAGGREGATE_INPUT = Yes
    GROUP_BY = _h3index
    CLEANING_TOLERANCE = Automatic
    CONNECT_Z_MODE = First Wins
    AREA -> PointOnAreaOverlayer_2 [AREA]
Note: Jointure des arrondissements et stationnements pour l'hexagone
PointOnAreaOverlayer_2
    DEAGGREGATE_INPUT = Yes
    OV_ATTR = _overlaps
    POLYS_FIRST = NO
    AREA -> AttributeCreator_2
Note: Création des attributs de densité
AttributeCreator_2
    ATTR_TABLE = SET_TO Densité_stationnement (real64) = @Evaluate(@Value(nbre_site_stationnement) / @Value(_h3index))
    -> AttributeKeeper
Note: Pour supprimer les colonnes d'attributs non nécessaires
AttributeKeeper
    CREATE_BULK_MODE_FEATURES = NO
    KEEP_ATTRS = Densité_stationnement,NOM,TYPE
    -> EsriReprojector_5
Note: Reprojection en 3857
EsriReprojector_5
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_NAME = <None>
    INTERPOLATION_TYPE = ,NearestNeighbor
    RASTER_CELL_SIZE_LOOKUP = ,PreserveCells
    RASTER_TOLERANCE = 0.0
    SOURCE = ESRIWKT|GCS_WGS_1984|GEOGCS["GCS_WGS_1984",DATUM["D_WGS_1984",SPHEROID["WGS_1984",6378137.0,298.257223563]],PRIMEM["Greenwich",0.0],UNIT["Degree",0.0174532925199433]]
    INTERPOLATION_TYPE_NAME = Nearest Neighbor
    RASTER_CELL_SIZE = Preserve Cells
    REPROJECTED -> Denssité_hexagon (writer POSTGIS_4)
Denssité_hexagon (writer POSTGIS_4)
    attributes: densité_stationnement float8, nom varchar, type varchar
